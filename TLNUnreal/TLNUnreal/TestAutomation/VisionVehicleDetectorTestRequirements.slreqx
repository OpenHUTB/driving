# VisionVehicleDetectorTestRequirements

## #1: scenario_LFACC_01_Curve_DecelTarget (Functional)
| Test Description | Test Requirements |
| --- | --- |
| Test YOLOv2 vehicle detector in automatic deceleration scenario on a straight road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 · Test YOLOv2 vehicle detector on a curved road scenario with ego vehicle in the left lane and with a lead vehicle. · Initial velocity of ego vehicle is set to 22m/s. · Lead vehicle moves at a constant velocity of 22 m/s for 11s, then decreases velocity by 3.5m/s in 2s with deceleration of -1.7 m/s^2 | · Number of false positives should be less than 1 · Number of true positives should be less than the number of actors present in the frame. · Sum of true positives and false negatives should be equal to number of actors present in the frame. · Avg precision should be greater than 80% · Avg miss rate should be less than 20% |

## #2: scenario_LFACC_02_Curve_AutoRetarget (Functional)
| Test Description | Test Requirements |
| --- | --- |
| Test YOLOv2 vehicle detector in automatic retarget test scenario on a curved road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 · Test YOLOv2 vehicle detector on a curved road scenario with ego vehicle in the left lane. · Initial velocity of ego vehicle is set to 15m/s. · A lead vehicle and a slow-moving vehicle are present in the scenario. · Lead vehicle travels in ego lane with 13.9m/s and changes lane at 46m to overtake the slow-moving vehicle in it’s lane. | · Number of false positives should be less than 1 · Number of true positives should be less than the number of actors present in the frame. · Sum of true positives and false negatives should be equal to number of actors present in the frame. · Avg precision should be greater than 80% · Avg miss rate should be less than 20% |

## #3: scenario_LFACC_03_Curve_StopnGo (Functional)
| Test Description | Test Requirements |
| --- | --- |
| Test YOLOv2 vehicle detector in stop and go test scenario on curved road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 · Test YOLOv2 vehicle detector on a curved road scenario with ego vehicle in the left lane · Initial velocity of ego vehicle is set to 22m/s. · Five Target vehicles are present in the scenario. · Lead vehicle travels with 13.6m/s for 4s, then slows down to 8m/s, and after 10s increase its velocity to 13m/s in ego lane. · Two slow moving vehicles travel with 8m/s in the lanes adjacent to ego lane. · Two fast moving vehicles travel with 15m/s in the lanes adjacent to ego lane. | · Number of false positives should be less than 6 · Number of true positives should be less than 6 · Number of misses should be less than 6 · Avg precision should be greater than 80% · Avg miss rate should be less than 20% |

## #4: scenario_LFACC_04_Curve_CutInOut (Functional)
| Test Description | Test Requirements |
| --- | --- |
| Test YOLOv2 vehicle detector in cut in and out test scenario on curved road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 · Test YOLOv2 vehicle detector on a curved road scenario with ego vehicle in the left lane · Initial velocity of ego vehicle is set to 20.6m/s. · Three target vehicles are present in the scenario. · Fast moving vehicle travels with 18m/s in ego lane. · Slow moving vehicle travels with 11.1m/s in the lane adjacent to ego lane. · Passing vehicle starts traveling in the lane adjacent to ego lane with 19.6m/s. Then, to overtake a slow-moving vehicle, it cuts into ego lane and then cuts out after the overtake. | · Number of false positives should be less than 1 · Number of true positives should be less than the number of actors present in the frame. · Sum of true positives and false negatives should be equal to number of actors present in the frame. · Avg precision should be greater than 80% · Avg miss rate should be less than 20% |

## #5: scenario_LFACC_05_Curve_CutInOut_TooClose (Functional)
| Test Description | Test Requirements |
| --- | --- |
| Test YOLOv2 vehicle detector in aggressive cut in and out test scenario on curved road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 · Test vision vehicle detector on a curved road scenario with ego vehicle in the left lane · Initial velocity of ego vehicle is set to 20.6m/s. · Three target vehicles are present in the scenario. · Fast moving vehicle travels with 18m/s in ego lane. · Slow moving vehicle travels with 14m/s in the lane adjacent to ego lane. · Passing vehicle starts traveling in the lane adjacent to ego lane with 19.6m/s. Then, to overtake a slow-moving vehicle, it cuts into ego lane and then cuts out after the overtake. | · Number of false positives should be less than 1 · Number of true positives should be less than the number of actors present in the frame. · Sum of true positives and false negatives should be equal to number of actors present in the frame. · Avg precision should be greater than 80% · Avg miss rate should be less than 20% |

## #6: scenario_LFACC_06_Straight_StopandGoLeadCar (Functional)
| Test Description | Test Requirements |
| --- | --- |
| Test YOLOv2 vehicle detector in stop and go test scenario on straight road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 · Test YOLOv2 vehicle detector on a straight road with ego vehicle in the left lane and a lead vehicle in the same lane. · Initial velocity of ego vehicle is set to 25m/s. · Initially, the lead vehicle is in halt state and after 4.5s, it starts travelling with 15 m/s and increases its speed to 22m/s later. | · Number of false positives should be less than 1 · Number of true positives should be less than the number of actors present in the frame. · Sum of true positives and false negatives should be equal to number of actors present in the frame. · Avg precision should be greater than 80% · Avg miss rate should be less than 20% |

## #14: scenario_VVD_01_Curve_FiveVehicles (Functional)
| Test Description | Test Requirements |
| --- | --- |
| Test YOLOv2 vehicle detector on a curved road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 · Test YOLOv2 vehicle detector on a curved road scenario with ego vehicle in the left lane. · Initial velocity of ego vehicle is set to 14m/s. · Four target vehicles are present in the scenario. · Lead vehicle travels with 20m/s in ego lane and other vehicles travel with 14m/s in the lanes adjacent to ego lane. | · Number of false positives should be less than 1 · Number of true positives should be less than the number of actors present in the frame. · Sum of true positives and false negatives should be equal to number of actors present in the frame. · Avg precision should be greater than 80% · Avg miss rate should be less than 20% |

## #16: scenario_FVSF_01_Curve_FourVehicles (Functional)
| Test Description | Test Requirements |
| --- | --- |
| Test YOLOv2 vehicle detector on curved road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 · Test YOLOv2 vehicle detector on a curved road scenario with ego vehicle in the right lane. · Initial velocity of ego vehicle is set to 16m/s. · Three target vehicles are present in the scenario. · Lead vehicle travels with 19.6m/s in ego lane. Then, it cuts into adjacent lane to overtake slow-moving vehicle present in the same lane, and then cuts out to ego lane. · A slow-moving vehicle travel with 11.1m/s in the ego lane. · Another target vehicle travel with 11.1m/s in the adjacent lane. | · Number of false positives should be less than 1 · Number of true positives should be less than the number of actors present in the frame. · Sum of true positives and false negatives should be equal to number of actors present in the frame. · Avg precision should be greater than 40% · Avg miss rate should be less than 70% |

## #17: scenario_FVSF_02_Straight_FourVehicles (Functional)
| Test Description | Test Requirements |
| --- | --- |
| Test YOLOv2 vehicle detector on straight road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 · Test YOLOv2 vehicle detector on a straight road scenario with ego vehicle in the left lane. · Initial velocity of ego vehicle is set to 16m/s. · Three Target vehicles are present in the scenario. · Lead vehicle starts travelling with 15m/s, then travels with constant acceleration to reach to 22m/s velocity. · The other two target vehicles start travelling with 16m/s and then travels with constant acceleration to reach to 22m/s velocity in adjacent lanes. | · Number of false positives should be less than 1 · Number of true positives should be less than the number of actors present in the frame. · Sum of true positives and false negatives should be equal to number of actors present in the frame. · Avg precision should be greater than 75% · Avg miss rate should be less than 25% |

## #18: scenario_FVSF_03_Curve_SixVehicles (Functional)
| Test Description | Test Requirements |
| --- | --- |
| Test YOLOv2 vehicle detector Stop and go test in curved road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 · Test YOLOv2 vehicle detector on a curved road scenario with ego vehicle in the left lane. · Initial velocity of ego vehicle is set to 14m/s. The ego vehicle travels with varied velocities. · Five Target vehicles are present in the scenario. · Lead vehicle travels with 13.6m/s for 4s, then slows down to 8m/s, and after 10s increase its velocity to 13m/s in ego lane. · Two slow moving vehicles travel with 8m/s in the lanes adjacent to ego lane. · Two fast moving vehicles travel with 15m/s in the lanes adjacent to ego lane. | · Number of false positives should be less than the number of actors present in the frame. · Number of true positives should be less than the number of actors present in the frame. · Sum of true positives and false negatives should be equal to number of actors present in the frame. · Avg precision should be greater than 75% · Avg miss rate should be less than 30% |
