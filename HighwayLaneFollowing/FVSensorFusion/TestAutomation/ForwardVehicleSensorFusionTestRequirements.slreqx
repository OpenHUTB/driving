# ForwardVehicleSensorFusionTestRequirements

## #1: scenario_LFACC_01_Curve_DecelTarget (Functional)
| Test Description | Test Requirements |
| --- | --- |
| Automatic Deceleration Test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 · Test forward vehicle sensor fusion on a curved road scenario with ego vehicle in the left lane with a lead vehicle. · Lead vehicle travels with an initial velocity of 22m/s for 11s and decreases it’s velocity by 3.5 m/s in 2s with deceleration of -1.7 m/s^2. | The maximum expected GOSPA value should not exceed 35, given the GOSPA properties as below, Alpha = 2 Order = 2 Switching Penalty = 0 Cut Off Distance = 30 |

## #2: scenario_LFACC_02_Curve_AutoRetarget (Functional)
| Test Description | Test Requirements |
| --- | --- |
| Automatic retarget test in curved road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 · Test forward vehicle sensor fusion on a curved road scenario with ego vehicle in the left lane with two other vehicles in its lane. · Lead vehicle travels in ego lane with 13.9m/s with initial head of 38m and changes lane at 46m to overtake the slow-moving vehicle in its lane. · Slow moving vehicle travels with a velocity of 10m/s in the ego lane with the initial headway of 60m. | The maximum expected GOSPA value should not exceed 35, given the GOSPA properties as below, Alpha = 2 Order = 2 Switching Penalty = 0 Cut Off Distance = 30 |

## #3: scenario_LFACC_03_Curve_StopnGo (Functional)
| Test Description | Test Requirements |
| --- | --- |
| Stop and go test in curved road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 · Test forward vehicle sensor fusion on a curved road scenario with ego vehicle in the left lane and other five vehicles in the scenario. · Lead vehicle travels with initial velocity for 4s, then slows down to 8m/s and after 10s increase its velocity to 13m/s in ego lane. · Slow moving vehicle 1 and slow moving vehicle 2 travels with a set velocity of 8m/s in the adjacent lane of the ego vehicle with initial headway of 1100 and 1060 respectively. · Fast moving vehicle 1 and fast moving vehicle 2 travels with a set velocity of 15m/s in the adjacent ego lane with initial headway of 5m and 40m respectively. | The maximum expected GOSPA value should not exceed 40, given the GOSPA properties as below, Alpha = 2 Order = 2 Switching Penalty = 0 Cut Off Distance = 30 |

## #4: scenario_LFACC_04_Curve_CutInOut (Functional)
| Test Description | Test Requirements |
| --- | --- |
| Cut in and out test in curved road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 · Test forward vehicle sensor fusion on a curved road scenario with ego vehicle in the left lane and a vehicle cuts into the ego lane which initially travels in adjacent lane of ego. · Passing vehicle starts its travels in lane that is adjacent to ego lane. Then, to overtake a slow-moving vehicle it cuts into ego lane and then cuts out after the overtake. · Slow moving vehicle travels in the adjacent ego lane with initial headway of 110m. · Fast moving vehicle travels in the ego lane with initial velocity of 18m/s with initial headway of 90m. | The maximum expected GOSPA value should not exceed 35, given the GOSPA properties as below, Alpha = 2 Order = 2 Switching Penalty = 0 Cut Off Distance = 30 |

## #5: scenario_LFACC_06_Straight_StopandGoLeadCar (Functional)
| Test Description | Test Requirements |
| --- | --- |
| Stop and Go test in straight road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 · Test forward vehicle sensor fusion on a straight road scenario with ego vehicle in the left lane and a vehicle that is initially stopped and starts after some time in the ego lane. · Lead vehicle is in halt state at first in ego lane with headway time of 2.2s. After 4.5s, it starts travelling with 15 m/s and increases its speed to 22m/s later. | The maximum expected GOSPA value should not exceed 35, given the GOSPA properties as below, Alpha = 2 Order = 2 Switching Penalty = 0 Cut Off Distance = 30 |

## #6: scenario_LFACC_05_Curve_CutInOut_TooClose (Functional)
| Test Description | Test Requirements |
| --- | --- |
| Cut in and out test in curved road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 · Test forward vehicle sensor fusion on a curved road scenario with ego vehicle in the left lane and a vehicle cuts into the ego lane and comes close to ego vehicle. · Passing vehicle starts its travels in lane that is adjacent to ego lane. Then, to overtake a slow-moving car it cuts into ego lane, comes close to ego car and then cuts out after the overtake. · Slow moving vehicle travels in the adjacent ego lane with initial headway of 50m. · Fast moving vehicle travels in the ego lane with initial velocity of 18m/s with initial headway of 45m. | The maximum expected GOSPA value should not exceed 35, given the GOSPA properties as below, Alpha = 2 Order = 2 Switching Penalty = 0 Cut Off Distance = 30 |

## #14: scenario_FVSF_01_Curve_FourVehicles (Functional)
| Test Description | Test Requirements |
| --- | --- |
| Four vehicles in curved road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 · Test forward vehicle sensor fusion on a curved road scenario with ego vehicle in the right lane and the lead vehicle cuts out of the the ego lane to overtake a slow-moving vehicle in ego lane. · Lead vehicle starts its travel in the ego lane with initial velocity of 19.6 m/s. · Slow moving vehicle 1 travels in the ego lane at a set velocity of 11.1 m/s with initial headway of 50m. · Slow moving vehicle 2 travels in the adjacent ego lane at a set velocity of 18 m/s with initial headway of 45m. | The maximum expected GOSPA value should not exceed 35, given the GOSPA properties as below, Alpha = 2 Order = 2 Switching Penalty = 0 Cut Off Distance = 30 |

## #16: scenario_FVSF_02_Straight_FourVehicles (Functional)
| Test Description | Test Requirements |
| --- | --- |
| Four vehicles in straight road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 · Test forward vehicle sensor fusion on a straight road scenario with ego vehicle in the left lane and the lead vehicle along with other two vehicles in the adjacent lane first travel with constant velocity and then increase their velocities. · Initial velocity of lead vehicle is 15m/s. · Vehicle1 travels with an initial velocity of 16m/s with initial headway of 1100m in adjacent lane to ego. · Vehicle 2 travels with an initial velocity of 16m/s with initial headway of 1160m in adjacent lane to ego. | The maximum expected GOSPA value should not exceed 35, given the GOSPA properties as below, Alpha = 2 Order = 2 Switching Penalty = 0 Cut Off Distance = 30 |

## #19: scenario_FVSF_03_Curve_SixVehicles (Functional)
| Test Description | Test Requirements |
| --- | --- |
| Six Vehicles in Curved Road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 · Test forward vehicle sensor fusion on a curved road scenario with ego vehicle in the left lane and other five vehicles in the scenario. · Ego vehicle travels in lane 3 and varies its velocity as if it is controlled in closed loop simulation. · Lead car travels initially with a velocity of 14 m/s for 4 seconds and reduces its velocity to 8 m/s and then again increases to 13 m/s after 10 seconds. · Slow moving vehicle 1 travels in lane 4 with an initial velocity of 8m/s with initial headway of 1100m in adjacent lane to ego. · Slow moving vehicle 2 travels in lane 4 with an initial velocity of 8 m/s with initial headway of 1060m in adjacent lane to ego. · Fast car 1 travels in lane 2 with a constant velocity of 15 m/s. · Fast car 2 follows Fast car 1 in lane 2 with a constant velocity of 15 m/s. | The maximum expected GOSPA value should not exceed 35, given the GOSPA properties as below, Alpha = 2 Order = 2 Switching Penalty = 0 Cut Off Distance = 30 |

## #20: scenario_FVSF_04_Straight_ThreeVehicles (Functional)
| Test Description | Test Requirements |
| --- | --- |
| Three vehicles in straight road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 · Test forward vehicle sensor fusion on a straight road scenario with ego vehicle in the left lane and the lead vehicle along with another vehicle in the adjacent lane. The objective of this test scenario is to find whether the tracker recognizes the two tracks or not. · Initial velocity of lead vehicle is 16m/s. · Other target vehicle initial speed is 16 m/s and travels with constant velocity in adjacent lane to ego lane. | The maximum expected GOSPA value should not exceed 0 after the initial delay of the tracker i.e. around 0.2 seconds, given the GOSPA properties as below, Alpha = 2 Order = 2 Switching Penalty = 0 Cut Off Distance = 30 |

## #21: scenario_FVSF_05_Straight_TwoVehicles (Functional)
| Test Description | Test Requirements |
| --- | --- |
| Four vehicles in straight road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 · Test forward vehicle sensor fusion on a straight road scenario with ego vehicle in the left lane and the target vehicle travels in right adjacent lane of ego. The objective of this test scenario is that ego should be able to detect the free lane and move forward. · Initial velocity of another target vehicle is 16 m/s and travels with constant velocity. | The maximum expected GOSPA value should not exceed 0 after the initial delay of the tracker i.e. around 0.2 seconds, given the GOSPA properties as below, Alpha = 2 Order = 2 Switching Penalty = 0 Cut Off Distance = 30 |
