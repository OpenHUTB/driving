# HighwayLaneFollowingTestRequirements

## 1: scenario_LFACC_01_Curve_DecelTarget (Functional)
| Test Description | Target vehicles | Requirements on Ego vehicle |
| --- | --- | --- |
| Automatic Deceleration Test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 | Lead vehicle: Initial velocity: 22m/s Headway: 44m Event: Lead vehicle moves at a constant velocity of 22 m/s for 11s, then decreases velocity by 3.5m/s in 2s with deceleration of -1.7 m/s^2 | Initial velocity: 22m/s Lateral deviation < 0.45m Time gap > 0.8s Expected behavior: Ego vehicle should decelerate to maintain minimum time gap from lead vehicle. |

## 2: scenario_LFACC_02_Curve_AutoRetarget (Functional)
| Test Description | Target vehicles | Requirements on Ego vehicle |
| --- | --- | --- |
| Automatic retarget test in curved road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 | Lead vehicle: Initial velocity: 13.9m/s Headway: 38m Event: Lead vehicle travels in ego lane with 13.9m/s and changes lane at 46m to over take the slow moving vehicle in it’s lane. Slow moving vehicle: Set velocity: 10m/s Headway: 60m Lane: Ego lane | Initial velocity: 15m/s Lateral deviation < 0.45m Time gap > 0.8s Expected behavior: Ego vehicle should decelerate to maintain safety time gap from lead vehicle. After the lead vehicle moves out of its lane, it should retarget and maintain the safety time gap from slow moving vehicle which is now becomes the new lead vehicle. |

## 3: scenario_LFACC_03_Curve_StopnGo (Functional)
| Test Description | Target vehicles | Requirements on Ego vehicle |
| --- | --- | --- |
| Stop and go test in curved road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 | Lead vehicle: Initial velocity: 13.6m/s Headway: 50m Event: Lead vehicle travels with initial velocity for 4s, then slows down to 8m/s and after 10s increase its velocity to 13m/s in ego lane. Slow moving vehicle - 1: Set velocity: 8m/s Headway: 1100m Lane: Adjacent to ego lane Slow moving vehicle - 2: Set velocity: 8m/s Headway: 1060m Lane: Adjacent to ego lane Fast moving vehicle - 1: Set velocity: 15m/s Headway: 5m Lane: Adjacent to ego lane Fast moving vehicle - 2: Set velocity: 15m/s Headway: 40m Lane: Adjacent to ego lane | Initial velocity: 14m/s Lateral deviation < 0.45m Time gap > 0.8s Expected behavior: Ego vehicle should first decelerate when lead vehicle slows down and then accelerate when lead vehicle increase its velocity such that it maintains safety time gap from lead vehicle while following the lanes. |

## 4: scenario_LFACC_04_Curve_CutInOut (Functional)
| Test Description | Target Vehicles | Requirements on Ego vehicle |
| --- | --- | --- |
| Cut in and out test in curved road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 | Fast moving vehicle: Initial velocity: 18m/s Headway: 90m Lane: Ego lane Passing vehicle: Initial velocity: 19.6m/s Headway: 60m Event: Passing vehicle starts its travels in lane that is adjacent to ego lane. Then, to overtake a slow-moving vehicle it cuts into ego lane and then cuts out after the overtake. Slow moving vehicle: Initial velocity: 11.1m/s Headway: 110m Lane: Adjacent to ego lane | Initial velocity: 20.6m/s Lateral deviation < 0.45m Time gap > 0.8s Expected behavior: Ego vehicle should respond to the passing vehicle that cuts into its lane to avoid the collision and to maintain safety time gap while following the lanes. |

## #5: scenario_LFACC_05_Curve_CutInOut_TooClose (Functional)
| Test Description | Target vehicles | Requirements on Ego vehicle |
| --- | --- | --- |
| Cut in and out test in curved road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 | Fast moving vehicle: Initial velocity: 18m/s Headway: 45m Event: Fast moving vehicle travels with its initial velocity in ego lane. Passing vehicle: Initial velocity: 19.6m/s Headway: 30m Event: Passing vehicle starts its travels in lane that is adjacent to ego lane. Then, to overtake a slow-moving car it cuts into ego lane, comes close to ego car and then cuts out after the overtake. Slow moving vehicle: Initial velocity: 14m/s Headway: 50m Lane: Adjacent to ego lane. | Initial velocity: 20.6m/s Lateral deviation < 0.45m Time gap > 0.8s Expected behavior: Ego vehicle should respond to the passing vehicle that cuts into its lane closely, to avoid the collision and to maintain safety time gap while following the lanes. |

## #6: scenario_LFACC_06_Straight_StopandGoLeadCar (Functional)
| Test Description | Target vehicles | Requirements on Ego vehicle |
| --- | --- | --- |
| Stop and Go test in straight road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 | Lead vehicle: Initial velocity: 0m/s Headway time: 2.2s Event: Lead vehicle is in halt state at first in ego lane. After 4.5s, it starts travelling with 15 m/s and increases its speed to 22m/s later. | Initial Velocity: 25m/s Lateral deviation < 0.45m Time gap > 0.8s Expected behavior: Ego vehicle should respond to the lead vehicle that is present in its lane in stop state, to avoid the collision and to maintain safety time gap while following the lanes. |

## #8: scenario_LF_01_Straight_RightLane (Functional)
| Test Description | Target vehicles | Requirements on Ego vehicle |
| --- | --- | --- |
| Lane following test in straight road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 | No target vehicles present in the scenario. | Initial Velocity: 15m/s Lateral deviation < 0.45m Expected behavior: Ego vehicle should follow the lanes. |

## #9: scenario_LF_02_Straight_LeftLane (Functional)
| Test Description | Target vehicles | Requirements on Ego vehicle |
| --- | --- | --- |
| Lane following test in straight road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 | No Target vehicles present in the scenario | Initial velocity: 15m /s Lateral deviation < 0.45m Expected behavior: Ego vehicle should follow the lanes. |

## #10: scenario_LF_03_Curve_LeftLane (Functional)
| Test Description | Target vehicles | Requirements on Ego vehicle |
| --- | --- | --- |
| Lane following test in curved road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 | No target vehicles present in the scenario | Initial Velocity: 20.6m/s Lateral deviation < 0.45m Expected behavior: Ego vehicle should follow the lanes. |

## #11: scenario_LF_04_Curve_RightLane (Functional)
| Test Description | Target Vehicles | Requirements on Ego vehicle |
| --- | --- | --- |
| Lane following test in curved road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 | No target vehicles present in the scenario | Initial velocity: 20.6 m/s Lateral deviation < 0.45m Expected behavior: Ego vehicle should follow the lanes. |
