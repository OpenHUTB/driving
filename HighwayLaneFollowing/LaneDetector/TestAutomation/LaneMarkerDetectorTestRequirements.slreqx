# LaneMarkerDetectorTestRequirements

## #2: scenario_LD_02_Curve_SixVehicles (Functional)
| Test Description | Test Requirements |
| --- | --- |
| Test lane marker detector on a curved road when one or more vehicles obstruct the ego vehicle’s lane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 · Test lane marker detector on a curved road scenario with ego vehicle in the left lane. · Five target vehicles are present in the scenario. · Lead vehicle slows down in front of ego vehicle while other vehicles travels in the adjacent lanes. · Initial Velocities are set to 20.6m/s. | · Deviation between the detected left lane marking and the corresponding ground truth must be less than 0.25m. · Deviation between the detected right lane marking and the corresponding ground truth must be less than 0.25m. |

## 1: scenario_LF_01_Straight_RightLane (Functional)
| Test Description | Test Requirements |
| --- | --- |
| Test lane marker detector on a straight road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 · Test lane marker detector on a straight road scenario with ego vehicle in the right most lane. · No target vehicles are present in the scenario. · Initial Velocity is set to 15m/s. | · Deviation between the detected left lane marking and the corresponding ground truth must be less than 0.25m. · Deviation between the detected right lane marking and the corresponding ground truth must be less than 0.25m. |

## 2: scenario_LF_02_Straight_LeftLane (Functional)
| Test Description | Test Requirements |
| --- | --- |
| Test lane marker detector on a straight road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 · Test lane marker detector on a straight road scenario with ego vehicle in the left lane. · No target vehicles are present in the scenario. · Initial Velocity is set to 15m/s. | · Deviation between the detected left lane marking and the corresponding ground truth must be less than 0.25m. · Deviation between the detected right lane marking and the corresponding ground truth must be less than 0.25m. |

## 3: scenario_LF_03_Curve_LeftLane (Functional)
| Test Description | Test Requirements |
| --- | --- |
| Test lane marker detector on a curved road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 · Test lane marker detector on a curved road scenario with ego vehicle in the left lane. · No target vehicles are present in the scenario. · Initial Velocity is set to 20.6m/s. | · Deviation between the detected left lane marking and the corresponding ground truth must be less than 0.25m. · Deviation between the detected right lane marking and the corresponding ground truth must be less than 0.25m. |

## 4: scenario_LF_04_Curve_RightLane (Functional)
| Test Description | Test Requirements |
| --- | --- |
| Test lane marker detector on a curved road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 · Test lane marker detector on a curved road scenario with ego vehicle in the right most lane. · No target vehicles are present in the scenario. · Initial Velocity is set to 20.6m/s. | · Deviation between the detected left lane marking and the corresponding ground truth must be less than 0.25m. · Deviation between the detected right lane marking and the corresponding ground truth must be less than 0.25m. |

## #12: scenario_LD_01_Curve_ThreeVehicles (Functional)
| Test Description | Test Requirements |
| --- | --- |
| Test lane marker detector on a curved road when one or more vehicles obstruct the ego vehicle’s lane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 · Test lane marker detector on a curved road scenario with ego vehicle in the left lane. · Two target vehicles, a passing car and slow-moving car are present in the scenario. · Passing car overtakes the slow-moving car by cutting into ego vehicle's lane. · Initial Velocities are set to 20.6m/s. | · Deviation between the detected left lane marking and the corresponding ground truth must be less than 0.25m. · Deviation between the detected right lane marking and the corresponding ground truth must be less than 0.25m. |
